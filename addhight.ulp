#include "Libdesy.lib"

string technologien[], t[];
int allHightProvided;
int hightprovided;
int someprovided;
int AllpackagesHaveHightToProvide;
int gotHightAttrb;

string extractDimension(string description) {
  string z;
  if(strxstr(description,"<dimensions>") >= 0) {
    string xml = strsub(description,strxstr(description,"<dimensions>"));
    z = xmlattribute(xml, "dimensions/z","val");
  }
  return z;
}

void msgPrompt(string msg) {
  dlgDialog("Nachricht"){
    dlgLabel(msg);
    dlgPushButton("+&OK") {
        dlgAccept();
      }
    dlgPushButton("-&Abbrechen") {
        dlgReject();
        exit(0);
      }
  };
}

void OpenPdf(string Description) {
  status("ExtractPdf()");
  int check = strxstr(Description,"Bautei.pdf");
  int start = check + 10;
  int start2;
  int len = 0;
  int len2;
  string returnval;
  
  start = strxstr(Description,
                  "\\\\\\\\[A-Za-z0-9\\s_.,\\\\+\\-\\*üäöÜÖÄ]{1,}\\.[pP][dD][fF]",
                  start+2*len+2,
                  len);
  returnval = strsub(Description,start, len );
  string temp[];
  if(fileglob(temp,returnval)<1)
    msgPrompt("hinterlegte Pdf-Datei nicht gefunden!!!");

  if(returnval) {
    system("cmd.exe /s /c start \" \" \""+ returnval +"\"\"\nexit");
  }
}


library(L){
  int laenge;
  string value;
  string Vari;
  string tech;
  string description;
  string packageWithoutHight;
  string deviceName;


  
  deviceset(DS) { // Device
    if(argv[1] == DS.name) {
      msgPrompt("Ende der Bibliothek");
      exit(0);
    }
    description = DS.description;
    deviceName = DS.name;
    allHightProvided = 1;
    AllpackagesHaveHightToProvide = 1;
    DS.devices(D) { // einzelne Variaten -> Package
      hightprovided = 1;
      someprovided = 1;
      gotHightAttrb = 0;
      int Anzahl_Technologien_Device = strsplit(t, D.technologies, ' ');
        for(int i = 0; i<Anzahl_Technologien_Device;i++) {
          D.attributes(A, t[i]) { //einzelne Technologie für Variante
            if(A.name == "HEIGHT") {
              gotHightAttrb = 1;
              if(A.value != "") {
                  someprovided = 1;
                } else {
                  hightprovided = 0;
                }
          }
        }
        if(!hightprovided || !gotHightAttrb) {
          allHightProvided = 0;
          if(strxstr(extractDimension(D.package.description),"\\d{1,}(,|\\.)?\\d*") < 0) {
            AllpackagesHaveHightToProvide = 0;
            packageWithoutHight = D.package.name;
          }
        }
      }
    }
  }

  if(!allHightProvided && AllpackagesHaveHightToProvide){
    //dlgMessageBox("!allHightProvided && AllpackagesHaveHightToProvide");
    exit("run editbau.ulp -update;run editnext-dev-sym-pac;run addhight.ulp "+deviceName+";");
  }
  if(!allHightProvided && !AllpackagesHaveHightToProvide) {
    //msgPrompt("noch keine Höhe hinterlegt");
    OpenPdf(description);
    exit("EDIT '"+packageWithoutHight+".pac';run packagedesc.ulp "+deviceName+";");
  }
  if(allHightProvided) {
    //msgPrompt("run editnext-dev-sym-pac;run addhight.ulp "+deviceName+";");

    exit("run editnext-dev-sym-pac;run addhight.ulp "+deviceName+";");
  }

  msgPrompt("wie sind wir denn hier her gekommen??");

}
