/**
 *  \file uebersicht.ulp
 *  \author Jan Scholz
 *  \brief 	Dieses Programm zeigt eine Übersicht aller Bauteile einer alten
 *  				Bibliothek an, dort wird gezeigt ob bereits ein Überführung in
 *  				die neue Bibliothek statt gefunden hat.
 *  
 */

string DevicesetName1,DevicesetName2,devicesets[],libs[],libsPath[],tempString,Lib6path,tempArrayString[],Libraries[],isBib6[],isBearbeitet[],varianten[];
int Anfang, Ende,selectedVar,AnzahlDevicesets,AnzahlDevicesetsBearbeitet;

void formatDeviceName(string Device) {
	
	if(strrchr(Device,'*')!=-1) {
		DevicesetName1 = strsub(Device,0,strrchr(Device,'*'));
		DevicesetName2 = strsub(Device,strrchr(Device,'*')+1);
	} else { 
		DevicesetName1 = Device;
		DevicesetName2 = "";
	}
}

string EntferneHtml(string DerString) {
	while(strstr(DerString,"<")!=-1) {
				Anfang = strstr(DerString,"<");
				Ende = strstr(DerString,">");
				tempString = strsub(DerString,0,Anfang);
				tempString += strsub(DerString,Ende+1);
				DerString = tempString;
			}
	return DerString;
}		

string cutsubstring(string longString,string regex,int offset ) {
	int laenge;
	return strsub(longString,strxstr(longString,regex,offset,laenge),laenge);
}

string int2str(int number) {
	string temp;
	sprintf(temp,"%d",number);
	return temp;
}

void findLibraryPaths() {
	
	for(int k = 0; k < 10; k++) {
		if(strxstr(path_lbr[k],"[Ll]br_6")>=0) Lib6path = path_lbr[k] ;	
	}
	int n = fileglob(libsPath, Lib6path+"/*.lbr"); 
		for(int g=0;libsPath[g]!="";g++) {
			libs[g+1]=strsub(libsPath[g],0,strlen(libsPath[g])-4);
			strsplit(tempArrayString,libs[g+1],'/');
			for(int f=0;tempArrayString[f]!="";f++);
			libs[g+1]=tempArrayString[f-1];
			
		}
}

int foundObBt(string btname) {
	string HerstellerDaten_Orderbase;	
	int Anzahl_Eintraege_CsvDatei;
	string ID,CsvDatei_in_Zeilen[],Eintraege[];
	int ReturnV=0;
	string Fund_Kategorie2;
	string Fund_Kategorie3;
	string Fund_Kategorie4;
	string Char,temp[];
	if(fileglob(temp,"D:/Dropbox/DesyBib/Ulp_5/neuer ulps/uebrigeBauteile.csv")>0) 
		fileread(HerstellerDaten_Orderbase,"D:/Dropbox/DesyBib/Ulp_5/neuer ulps/uebrigeBauteile.csv");
	else
		fileread(HerstellerDaten_Orderbase,"H:/sze/Eagle6/Ulp_5/neuer ulps/uebrigeBauteile.csv");
		
	Anzahl_Eintraege_CsvDatei = strsplit(CsvDatei_in_Zeilen,HerstellerDaten_Orderbase,'\n');
	for(int i=0;i<strlen(btname);i++)  {
		if(cutsubstring(btname,".",i) == "*") Char = "[\\w\\d_\.\\s]{,7}";
		else Char = cutsubstring(btname,".",i);
		Fund_Kategorie2 += Char + "[_-\\s/\\\.\*]?";
		Fund_Kategorie3 +=  Char  + "[_-\\s/\\\.\*]?";
		if(i==1000) {
			break;

		}
	}
	for(i=0;i<=(strlen(btname)/2)+1;i++)  {
		Fund_Kategorie4 += cutsubstring(btname,".",i)+ "[_-\\s/\\\.\*]?";
	}
	for(int k=0;k<Anzahl_Eintraege_CsvDatei;k++) {
		strsplit(Eintraege,CsvDatei_in_Zeilen[k],';');
		if(strxstr(Eintraege[2],btname)>=0) {return 4;}
		else if(strxstr(Eintraege[2],Fund_Kategorie2)>=0) {if(ReturnV<3) ReturnV = 3;}
		else if(strxstr(Eintraege[2],Fund_Kategorie3)>=0) {if(ReturnV<2) ReturnV = 2;}
		else if(strxstr(Eintraege[2],Fund_Kategorie4)>=0) {if(ReturnV<1)ReturnV= 1;}
	}
		return ReturnV;
		
}

void menue() {
	dlgDialog("Übersicht") {
	
		dlgGridLayout {
		dlgCell (0, 0) dlgHBoxLayout {
			dlgVBoxLayout {
				dlgLabel("Anzahl Devicesets : "+int2str(AnzahlDevicesets));
				dlgLabel("bearbeitete Devicesets : "+int2str(AnzahlDevicesetsBearbeitet));
			}
			int done = (AnzahlDevicesetsBearbeitet*100)/AnzahlDevicesets;
			if(done < 33)	dlgLabel("<font size=7 color=#B40404>"+int2str(done)+"%");
			if(done > 33 & done < 66) dlgLabel("<font size=7 color=#86B404>"+int2str(done)+"%");
			if(done > 66)	dlgLabel("<font size=7 color=#04B404>"+int2str(done)+"%");
		}
		dlgCell (1, 0) dlgHBoxLayout {
			dlgVBoxLayout {dlgSpacing(800); }
			dlgListView("bearbeitet\tin Bib6\tBauteil\tDesc\tVarianten\tObTreffer",Libraries,selectedVar) exit("EDIT '"+devicesets[selectedVar]+".dev';");
		}
		}
	};
}
library(L){
	int x;
	int flag;
	string descString;
	string libra;
	string t[];
	findLibraryPaths();
	

	
	
	for(int h = 0;libsPath[h]!="";h++) {
		fileread(libra, libsPath[h]);
		
		x=0;
		
		L.devicesets(DSs) {
			formatDeviceName(DSs.name);
			if(strxstr(libra,"<deviceset name=\""+DSs.name+"\"")>0) isBib6[x]="X";	
			if(strxstr(libra,"<deviceset name=\""+DevicesetName1+"\\*"+DevicesetName2+"\"")>0) isBib6[x]="X";	
			x++;
		}
	}
	x = 0;
	
	
			
	L.devicesets(DSs) {
		devicesets[x] = DSs.name;

		flag = 0;
		DSs.devices(D) {
			varianten[x]+=D.name+",";
			int n = strsplit(t, D.technologies, ' ');
			D.attributes(A, t[0]) {
				if(A.name == "HERSTELLER_NR") {
					flag = 1;
				}
			}
		}
		if(flag) { 
			AnzahlDevicesetsBearbeitet++;
			isBearbeitet[x]="X";
		}
		Libraries[x] = isBearbeitet[x]+"\t"+isBib6[x];
		strsplit(tempArrayString,DSs.description,'\n');
		if(strxstr(tempArrayString[0],"<html>")>=0) descString = tempArrayString[1];
		else descString = tempArrayString[0];	
		Libraries[x]+="\t"+DSs.name+"\t"+cutsubstring(EntferneHtml(descString),"[^\\s].*",0)+"\t"+varianten[x]+"\t"+int2str(foundObBt(DSs.name));
		x++;
		
	}
	AnzahlDevicesets = x;
	menue();
}
