/**
 *  @file PlatzhalterErsetzen.ulp
 *  @brief 	Durch dieses Programm wird das Ersetzen von alten Bauteilen
 *  				der 4er Bibliothek von Eagle auf die neue 6er Bibliothek 
 *  				in älteren Platinen-Layouts vereinfacht.
 */
 
#include "Libdesy.lib"
 

string tempStrArr1[],tempStrArr2[],tempStr1,tempstr2,LibList;
int AenderungenGeschehen = FALSE;
int Counter;	
int index[]; /**< Some documentation for first. */
int position;
string ULP_PATH = "//win.desy.de/group/sze/public/Eagle_6+/ulp";
string out[];
string Pac_Sort_Arr[], Val_Sort_Arr[], Pac_Sort, Val_Sort;
string HerstellerNummer[], Val[], Beschreibung[], Package[], Hersteller[], Vorzug[],OrderbaseNummer[],DeviceName[],Prefix[];
int Bauteile;								///< Anzahl Bauteile

enum {	ORDERBASE_NUMMER 	= 0,    ///< indize für Bauteil-Attribut im Datensatz
				PART_NAME 				= 1,		///< indize für Bauteil-Attribut im Datensatz
				PACKAGE 					= 2,    ///< indize für Bauteil-Attribut im Datensatz
				VALUE						  = 3,    ///< indize für Bauteil-Attribut im Datensatz
				VALU 							= 4,		///< indize für Bauteil-Attribut im Datensatz
				HERSTELLER 				= 5,    ///< indize für Bauteil-Attribut im Datensatz
				VORZUG 						= 6,    ///< indize für Bauteil-Attribut im Datensatz
				BESCHREIBUNG 			= 7,    ///< indize für Bauteil-Attribut im Datensatz
				PREFIX 						= 8,    ///< indize für Bauteil-Attribut im Datensatz
				LIBRARY 					= 9,    ///< indize für Bauteil-Attribut im Datensatz
				HERSTELLERNR 			= 10,   ///< indize für Bauteil-Attribut im Datensatz
				DATENBLATT 				= 11,   ///< indize für Bauteil-Attribut im Datensatz
				DEVICE_NAME 			= 12,   ///< indize für Bauteil-Attribut im Datensatz
				PINS 							= 13,		///< indize für Bauteil-Attribut im Datensatz
				SYMBOLS						= 14,		///< indize für Bauteil-Attribut im Datensatz
				VALUEON_OFF 			= 15,   ///< indize für Bauteil-Attribut im Datensatz
				ORIENTATION 			= 16,		///< indize für Bauteil-Attribut im Datensatz
				MIRRORED 					= 17,		///< indize für Bauteil-Attribut im Datensatz
				SHEET 						= 18,		///< indize für Bauteil-Attribut im Datensatz
				ID 								= 19,		///< indize für Bauteil-Attribut im Datensatz
				CHANGE_MODE				= 20		///< indize für Bauteil-Attribut im Datensatz
				};	

enum { 	NONE							= 0,		///<  Konstante für bessere Lesbarkeit
				COMPLETE 	  			= 1,    ///<  Konstante für bessere Lesbarkeit
				ATTR_SYM 	  			= 2,    ///<  Konstante für bessere Lesbarkeit
				PACK_ONLY 				= 3,    ///<  Konstante für bessere Lesbarkeit
				ATTR_ONLY 				= 4,    ///<  Konstante für bessere Lesbarkeit
				RECOVER     			= 5};		///<  Konstante für bessere Lesbarkeit

enum {  VAL = 0, 								///< Sortier-Modus 
				PAC = 1,								///< Sortier-Modus 
				VALPAC = 2};						///< Sortier-Modus 

int PartAttribOrder[] = {	ORDERBASE_NUMMER, ///< 
													HERSTELLER,
													HERSTELLERNR,
													VALU,
													VORZUG};
													
string att[]={"DATENBANKOB-NR", ///< Bauteil-Attribute hinterlegt für jedes neue Bauteil
							"HERSTELLER_NAME",
							"HERSTELLER_NR",
							"VAL",
							"ZE-VORZUG"};

string PartDataValueNames[] = {	"OrderbaseNummer",
																"P.name", 
																"P.device.package.name",
																"P.value",
																"Val",
																"Hersteller",
																"Vorzug",
																"Beschreibung",
																"P.device.prefix",
																"P.device.library",
																"HerstellerNummer",
																"Datenblatt",
																"P.device.name",
																"EingAenge/AusgAenge",
																"Symbols",
																"VALUE ON/OFF",
																"Orientation",
																"mirrored",
																"Sheet",
																"Id",
																"ChangeMode"};

string PartData[];          ///< Bauteil-DatensAetzen aus Schaltplan
string PartDataRecovery[];  ///< Bauteil-DatensAetzen aus Schaltplan
string PlaceholderOnly[];		///< Bauteil-DatensAetzen aus Schaltplan
int NoOfParts;              ///< Bauteil-DatensAetzen aus Schaltplan
int NoOfPlaceholders;				///< Bauteil-DatensAetzen aus Schaltplan

int evalChangeMode(string cMode) {
	if(cMode == int2str(NONE)) 				return	NONE;			
	if(cMode == int2str(COMPLETE))    return  COMPLETE;
	if(cMode == int2str(ATTR_SYM))    return  ATTR_SYM; 
	if(cMode == int2str(PACK_ONLY))   return  PACK_ONLY;
	if(cMode == int2str(ATTR_ONLY))   return  ATTR_ONLY;
	return 0;
} 


string getPartVal(string FullPartString, int pos) {
	string tempoarray[];
	strsplit(tempoarray,FullPartString,'\t');
	return tempoarray[pos];
}

string setPartVal(string FullPartString, int pos, string newVal) {
	string tempoarray[], newFullPartString;
	int n = strsplit(tempoarray,FullPartString,'\t');
	for(int i = 0; i <= n; i++) {	
		newFullPartString += (i == pos) ? newVal : tempoarray[i];
		newFullPartString += (i < n) ? "\t" : "";
	}
	return newFullPartString;
}
      

int partCmp(string part1, string part2) {	
	for(int i = PACKAGE; i <= PINS; i++) {
		if(getPartVal(part1,i) != getPartVal(part2,i)) {
			//debug(getPartVal(part1,i) +"\n!=\n"+ getPartVal(part2,i));
			return FALSE;
		}
	}
	return TRUE;
}

string exchangePart(string old_Part, string new_Part, int mode) {
	AenderungenGeschehen = TRUE;
	string returnval;
	switch(mode) {
		case 0 /* NONE */: {
							break;
						}
		case 1 /* COMPLETE */:	{
							returnval = setPartVal(	new_Part,
																			PART_NAME,
																			getPartVal(old_Part,PART_NAME));
							returnval = setPartVal(	returnval,
																			ORIENTATION,
																			getPartVal(old_Part,ORIENTATION));
							returnval = setPartVal(	returnval,
																			MIRRORED,
																			getPartVal(old_Part,MIRRORED));
							returnval = setPartVal(	returnval,
																			SHEET,
																			getPartVal(old_Part,SHEET));
							returnval = setPartVal(	returnval,
																			ID,
																			getPartVal(old_Part,ID));
							returnval = setPartVal(	returnval,
																			CHANGE_MODE,
																			int2str(COMPLETE));
							break;
						}	
		case 2 /* ATTR_SYM */:	{
								returnval = getPartVal(old_Part,PART_NAME) + "\t" +
								getPartVal(new_Part,DEVICE_NAME) + "\t" +
								getPartVal(old_Part,PACKAGE) + "\t" +
								getPartVal(new_Part,VALUE) + "\t" +
								getPartVal(new_Part,PREFIX) + "\t" +
								getPartVal(old_Part,LIBRARY) + "\t" +
								getPartVal(old_Part,HERSTELLER) + "\t" +
								getPartVal(old_Part,HERSTELLERNR) + "\t" +
								getPartVal(old_Part,VORZUG) + "\t" +
								getPartVal(old_Part,BESCHREIBUNG) + "\t" +
								getPartVal(old_Part,DATENBLATT) + "\t" +
								getPartVal(old_Part,ORDERBASE_NUMMER) + "\t" +
								int2str(ATTR_SYM) + "\t";
							break;
						}	
		case 3 /* PACK_ONLY */:	{
							returnval = getPartVal(old_Part,PART_NAME) + "\t" +
							getPartVal(new_Part,DEVICE_NAME) + "\t" +
							getPartVal(old_Part,PACKAGE) + "\t" +
							getPartVal(new_Part,VALUE) + "\t" +
							getPartVal(new_Part,PREFIX) + "\t" +
							getPartVal(old_Part,LIBRARY) + "\t" +
							getPartVal(old_Part,HERSTELLER) + "\t" +
							getPartVal(old_Part,HERSTELLERNR) + "\t" +
							getPartVal(old_Part,VORZUG) + "\t" +
							getPartVal(old_Part,BESCHREIBUNG) + "\t" +
							getPartVal(old_Part,DATENBLATT) + "\t" +
							getPartVal(old_Part,ORDERBASE_NUMMER) + "\t" +
							int2str(PACK_ONLY) + "\t";
							break;
						}	
		case 4 /* ATTR_ONLY */:	{
							returnval = setPartVal(	new_Part,
																			PART_NAME,
																			getPartVal(old_Part,PART_NAME));
							returnval = setPartVal(	returnval,
																			ORIENTATION,
																			getPartVal(old_Part,ORIENTATION));
							returnval = setPartVal(	returnval,
																			MIRRORED,
																			getPartVal(old_Part,MIRRORED));
							returnval = setPartVal(	returnval,
																			SHEET,
																			getPartVal(old_Part,SHEET));
							returnval = setPartVal(	returnval,
																			ID,
																			getPartVal(old_Part,ID));
							returnval = setPartVal(	returnval,
																			CHANGE_MODE,
																			int2str(ATTR_ONLY));
							break;
						}	
		case 5 /* RECOVER */: {
							returnval = setPartVal(	new_Part,
																			PART_NAME,
																			getPartVal(old_Part,PART_NAME));
							returnval = setPartVal(	returnval,
																			ORIENTATION,
																			getPartVal(old_Part,ORIENTATION));
							returnval = setPartVal(	returnval,
																			MIRRORED,
																			getPartVal(old_Part,MIRRORED));
							returnval = setPartVal(	returnval,
																			SHEET,
																			getPartVal(old_Part,SHEET));
							returnval = setPartVal(	returnval,
																			ID,
																			getPartVal(old_Part,ID));
							returnval = setPartVal(	returnval,
																			CHANGE_MODE,
																			int2str(NONE));
							break;
						}
		default : {
							returnval = old_Part;
							break;
						}
	}
	
	return returnval;
}


void changeAllidenticalParts(string template, string newPart, int mode) {
	for(int i = 0; i < NoOfParts; i++) {
		if(partCmp(template,PartData[i])) {
			PartData[i] = exchangePart(PartData[i],newPart,mode);
		}
	}
	for(int k = 0; k < NoOfPlaceholders; k++) {
		if(partCmp(template,PlaceholderOnly[k])) 
			PlaceholderOnly[k] = exchangePart(PlaceholderOnly[k],newPart,mode);
	}
}              


/**
 *  @brief Die vorsortierten DatensAetze werden mittels binAerer Suche nach dem Suchbegriff
 *  durchsucht
 *  
 *  @param [in] searchString Suchbegriff
 *  @param [in] SORTING      Welche Sortierung wird benutzt
 *  @return erster Index an dem die gesuchten Daten gefunden wurden im Datensatz
 */
int BTSearch(string searchString, int SORTING) {
	int index, lastindex, iteration, upper, Wildcard, length;
	lastindex = 0;
	string temp[], tempstr;
	index = int (Bauteile / 2);
	string db_entry;
	
	while(strxstr(searchString,"\\*") > -1) 
		searchString = strsub(searchString,0,strlen(searchString)-1);
			
	length = strlen(searchString);
	if(length <= 0) return -1;

	while(index != lastindex ) {
		iteration++;
		SORTING ? strsplit(temp,Pac_Sort_Arr[index],';') : strsplit(temp,Val_Sort_Arr[index],';'); 
		lastindex = index;
		//debug("searchString:" + searchString +"\nVergleichsstring: " + temp[0]+ "\niteration: " + int2str(iteration)+ "\nindex : " + int2str(index)+"\nCompare :" + int2str(cmpstr(searchString,temp[0])));
		db_entry = strsub(temp[0],START,length);
		//debug(db_entry + "\n" + searchString);
		switch (cmpstr(db_entry,searchString)) {
			case  1:  index -= int(Bauteile / (2 * pow(2,iteration)))+1;
								break;
			case  0:  upper = index;
								while(db_entry == searchString) {
									SORTING ? strsplit(temp,Pac_Sort_Arr[--upper],';') : 
														strsplit(temp,Val_Sort_Arr[--upper],';'); 
									db_entry = strsub(temp[0],START,length);
									//debug("db_entry:"+db_entry+"\nindex:"+int2str(index)+"\n"+"lastindex:"+int2str(lastindex)+"\n");
								}	//debug("Pac_Sort_Arr[upper--]:"+Pac_Sort_Arr[upper--]+"Pac_Sort_Arr[index]:"+Pac_Sort_Arr[index]+"\nupper--");
								return upper+1;
								break;
			case -1:	index += int(Bauteile / (2 * pow(2,iteration)))+1;
								break;
		}
		if((iteration - 2) > log2(Bauteile)) return -1;
		//debug("db_entry:"+db_entry+"\nindex:"+int2str(index)+"\n"+"lastindex:"+int2str(lastindex)+"\n");
	}
	return -1;
}
/**
 *  @brief 	Ein Suchergebnis wird noch einem zweiten Suchkriterium (Val) durchsucht
 *  @param [in] searchString Suchbegriff
 *  @param [in] Subject      Zu durchsuchender String (Liste von Bauteil-DatensAetzen)
 *  @return Liste von Bauteil-DatensAetzen die dem Suchkriterium genügen
 */
string refinedSearch(string searchString, string Subject) {
	string temp_arr1[], temp_arr2[], returnval;
	int length = strlen(searchString);

	for(int i = 0; i < strsplit(temp_arr1,Subject,'\n'); i++){
		strsplit(temp_arr2,temp_arr1[i],';');
		if(searchString == strsub(temp_arr2[1],0,length - 1));
			returnval += temp_arr1[i];
	}
		return returnval;
}

/**
 *  \brief Die Funktion vergleicht ob die Namen der Symbole zweier Bauteile identisch sind
 *  
 *  \param [in] Symbols1 Symbole von Part1 mit Kommata getrennt
 *  \param [in] Symbols2 Symbole von Part2 mit Kommata getrennt
 *  \return TRUE -> 1 = identisch, FALSE -> 0 = ungleich
 */
int symCmp(string Symbols1, string Symbols2) {
	string Sym1arr[], Sym2arr[];
	if(cmpstr(Symbols1,Symbols2) == 0)
		return TRUE;
	int syms = strsplit(Sym1arr,Symbols1,',');
	if(syms != strsplit(Sym2arr,Symbols2,','))
		return FALSE;
	for(int i = 0; i < syms; i++) {
		int Fund = FALSE;
		for(int k = 0; k < syms; k++) {
		/*debug("i="+int2str(i)+
						"\nk="+int2str(k)+
						"\nSym1arr[i]"+Sym1arr[i]+
						"\nSym2arr[k]"+Sym2arr[k]);*/
			if(cmpstr(Sym1arr[i],Sym2arr[k]) == 0) {
				Fund = TRUE;			
				break;
			}
		}
		if(Fund == FALSE) return FALSE;
	}
	return TRUE;
}

/**
 *  @brief Die Funktion evaluiert ob zwei Bauteile gleich sind, falls dies
 *  nicht der Fall ist wird der User gefragt ob trotzdem die beiden Bauteile getauscht 
 *  werden sollen
 *  
 *  @param [in] part1 erstes zu vergleichendes Bauteil
 *  @param [in] part2 zweites zu vergleichendes Bauteil
 *  @return 0 -> Bauteile nicht tauschen 1 -> Bauteile tauschen
 */
int Check(string part1, string part2) {

	int pin = getPartVal(part1, PINS) == getPartVal(part2, PINS);
	int pac = getPartVal(part1, PACKAGE) == getPartVal(part2, PACKAGE);
	int sym = symCmp(getPartVal(part1, SYMBOLS),getPartVal(part2, SYMBOLS));
	
	if(	pin && pac && sym){
		return TRUE;
	} else {
		int i = 1;
		return dlgDialog("Achtung"){
			dlgLabel(	"<html><font color=\"#FF0000\">Die Bauteile unterscheiden sich in einem oder "
							  "mehreren kritischen Parametern, soll wirklich umgetauscht werden ?");
			dlgGridLayout{
				dlgCell(0,0) 			dlgLabel("Unterschied");
				dlgCell(0,1) 			dlgLabel("altes Bauteil");
				dlgCell(0,2) 			dlgLabel("neues Bauteil");
				if(!pin) {
					dlgCell(i,0) 		dlgLabel("Anzahl EingAenge/AusgAenge");
					dlgCell(i,1)		dlgTextView(getPartVal(part1, PINS));
					dlgCell(i++,2)	dlgTextView(getPartVal(part2, PINS));
				}
				if(!pac) {
					dlgCell(i,0) 		dlgLabel("Package Name");
					dlgCell(i,1)		dlgTextView(getPartVal(part1, PACKAGE));
					dlgCell(i++,2)	dlgTextView(getPartVal(part2, PACKAGE));
				}
				if(!sym) {
					dlgCell(i,0) 		dlgLabel("verwendete/s Symbol/e");
					dlgCell(i,1)		dlgTextView(getPartVal(part1, SYMBOLS));
					dlgCell(i++,2)	dlgTextView(getPartVal(part2, SYMBOLS));
				}
			}
			dlgPushButton("Fortsetzen") {
				dlgAccept(TRUE);
				}
			dlgPushButton("Abbrechen") {
				dlgReject(FALSE);
			}
		};
	}
	return FALSE;
}




/**
 *  @brief Mit Hilfe dieser Funktion werden die DatensAetze der Bauteile aus dem Schaltplan
 *  angelegt
 *  
 */
void getPartData(){
status("getPartData()");


			
	if(schematic){
		schematic(S){
			S.parts(P) {
				if(strxstr(P.device.library,"(Spannungs_?[Vv]ersorgung)|[Vv]orlage") >= 0)
						continue; //In diesem fall handelt es sich um kein Bauteil
				string orientation;
				string seite;
				string symbols;
				int mirrored;
				P.instances(I) {
					orientation = real2str(I.angle,0);
					mirrored = I.mirror;
					seite = int2str(I.sheet);
				}
				int inout_int = 0;
				string attVal[];	
				P.attributes(A) {
					for(int i = 0; i < 5; i++)
						if(A.name == att[i]) attVal[i] = A.value;
				}
				string PackageName = ""; 
				if(P.device.package)  PackageName = P.device.package.name;
				P.device.gates(G) {
					if(strxstr(symbols,G.symbol.name) < 0)
						symbols +=(strlen(symbols) > 1 ? "," : "")+G.symbol.name;
					G.symbol.pins(I){
						inout_int++;
					}
				}
				PartData[NoOfParts] =   attVal[0] + "\t"
															+ P.name + "\t"
															+ PackageName + "\t"
															+ P.value + "\t"
															+ attVal[3] + "\t"
															+ attVal[1] + "\t"
															+ attVal[4] + "\t"
															+ trimws(strrep(cutsubstring(P.device.description,"[^\\n]{9,}\\n",0),"((&lt;)|<)/?[^\\n;<>]*((&gt;)|>)","",0,1)) + "\t"		//Beschreibung
															+ P.device.prefix + "\t"
															+ P.device.library + "\t"
															+ attVal[2] + "\t"
															+ cutsubstring(P.device.description,"file:\\\\[^\\n\"]*\\.[pP][dD][fF]",0) + "\t"		//Datenblatt
															+ P.device.name + "\t"
															+ int2str(inout_int) + "\t"
															+ symbols + "\t"
															+ P.deviceset.value + "\t" 
															+ orientation + "\t"
															+ (mirrored ? "true" : "false" )+ "\t"
															+ seite + "\t"
															+ int2str(NoOfParts) + "\t"
															+ int2str(NONE);
				PartDataRecovery[NoOfParts] = PartData[NoOfParts];
				if(strxstr(P.device.library,"Platzhalter") >= 0) 
					PlaceholderOnly[NoOfPlaceholders++] = PartData[NoOfParts];
				NoOfParts++;
			}
		}
	}
}

/**
 *  \brief Brief
 *  
 *  \param [in] Bezeichnung Suchparameter für Bezeichnung des Bauteils
 *  \param [in] Package     Suchparameter für Package des Bauteils
 *  \param [in] Hersteller  Suchparameter für Hersteller des Bauteils
 *  \param [in] OB_Nummer		Suchparameter für Orderbase-Nummer des Bauteils
 *  \param [in] vz          Sollen nur Vorzugsbauteile gezeigt werden ?
 *  \param [in] ignore_case Soll Groß- und Kleinschreibung berücksichtigt werden ?
 *  \param [in] PartNr      Das Bauteil welches getauscht werden soll (intern vergebene Nummer)
 *  \return Tabelle der Bauteile die die Suchkriterien erfüllen 
 *  				mit Tabulator separierte Attribute
 */
string createTable(
		string Bezeichnung, 
		string Package, 
		string Hersteller,
		string OB_Nummer,
		int vz, 
		int ignore_case, 
		int PartNr) {
		
 status("createTable()");
 string searchableFile = "\\\\win.desy.de\\group\\sze\\public\\Eagle_6+\\ulp\\Bauteile_nach_Package_sortiert.csv";
 string Ergebnisse[];
 string liste;
 int Zeile = 0;
 string t[];
	
	if(Package == "" && Bezeichnung == "" && Hersteller == "" && OB_Nummer == ""){
		dlgMessageBox(":Bitte geben Sie mindestens einen Suchbegriff für "
									"Hersteller, Bezeichnung, Package oder Orderbase-Nummer an");
		return "";
	}	
	Package = strrep(Package,"\\*","[^;\\n]*",0,1);
	Package = strrep(Package,"\\?","[^;\\n]",0,1);
	Bezeichnung = strrep(Bezeichnung,"\\*","[^;\\n]*",0,1);
	Bezeichnung = strrep(Bezeichnung,"\\?","[^;\\n]",0,1);
	Hersteller = strrep(Hersteller,"\\*","[^;\\n]*",0,1);
	Hersteller = strrep(Hersteller,"\\?","[^;\\n]",0,1);
	OB_Nummer = strrep(OB_Nummer,"\\*","[^;\\n]*",0,1);
	OB_Nummer = strrep(OB_Nummer,"\\?","[^;\\n]",0,1);
	
	/*debug("cmd.exe /c " + GREP_PATH + (ignore_case ? " -i " : " ") 
						+ "\"^[^;\\n]*" + Package + "[^;\\n]*;\""
						+ " \"" + searchableFile + "\" "
						+ " | " + GREP_PATH + (ignore_case ? " -i " : " ")
						+ "\"^\\([^;\\n]*;\\)\\{1\\}" + Bezeichnung + "\""
						+ " | " + GREP_PATH + (ignore_case ? " -i " : " ")
						+ "\"^\\([^;\\n]*;\\)\\{3\\}" + OB_Nummer + "\""
						+ " | " + GREP_PATH + (ignore_case ? " -i " : " ")
						+ "\"^\\([^;\\n]*;\\)\\{4\\}" + Hersteller + "\""
						+ " >\"" + EAGLE_HOME + "/out.txt\""); */
	
	system("cmd.exe /c " + GREP_PATH + (ignore_case ? " -i " : " ") 
						+ "\"^[^;\\n]*" + Package + "[^;\\n]*;\""
						+ " \"" + searchableFile + "\" "
						+ " | " + GREP_PATH + (ignore_case ? " -i " : " ")
						+ "\"^\\([^;\\n]*;\\)\\{1\\}" + Bezeichnung + "\""
						+ " | " + GREP_PATH + (ignore_case ? " -i " : " ")
						+ "\"^\\([^;\\n]*;\\)\\{3\\}" + OB_Nummer + "\""
						+ " | " + GREP_PATH + (ignore_case ? " -i " : " ")
						+ "\"^\\([^;\\n]*;\\)\\{4\\}" + Hersteller + "\""
						+ " >\"" + EAGLE_HOME + "/out.txt\"");
						
	fileread(Ergebnisse,EAGLE_HOME + "/out.txt");
	
	system("cmd.exe /c del \"" + EAGLE_HOME + "\\out.txt\"");

	
	while(Ergebnisse[Zeile] != "") {
	
		strsplit(t,Ergebnisse[Zeile],';');
		
		string device_name = 			t[2];    
		string prefix = 					t[8];           
		string libra = 						t[10];          
		string hersteller = 			t[4];       
		string herstellernr = 		t[5];     
		string vorzug = 					t[6];           
		string beschreibung = 		t[7];     
		string datenblatt = 			t[9];      
		string orderbase_nummer = t[3];
		string inout = 						t[11];
		string symbols = 					t[12];
		string valonoff= 				  t[13];
		string val =							t[1];
		string pac = 							t[0];
		liste += orderbase_nummer + "\t - \t" + pac + "\t" + val + "\t" + val + "\t" + hersteller
								 + "\t" + vorzug + "\t" + beschreibung + "\t" + prefix + "\t" + libra  
								 + "\t" + herstellernr + "\t" + datenblatt + "\t" + device_name 
								 + "\t" + inout + "\t" + symbols + "\t" + valonoff + "\n";

		Zeile++;
	}
	
	return liste;
}

string newDataset(int PartNr) {
	string temp[];
	string Dataset[], newDataset;
	strsplit(Dataset,PartData[PartNr],'\t');
	dlgDialog("neuer Datensatz") {
		dlgGridLayout {
			dlgCell(0, 0) {
				dlgVBoxLayout{
					for(int i = 0; i < 5; i++) {
						dlgLabel(PartDataValueNames[PartAttribOrder[i]]);
					}
				}
			}
			dlgCell(0, 1) {
				dlgVBoxLayout{
					dlgHBoxLayout{ 
						dlgSpacing(320);
					}
					for(int i = 0; i < 5; i++) {
						dlgStringEdit(Dataset[PartAttribOrder[i]]);
					}
				}
			}
		}
		dlgPushButton("&Nur dieses Bauteil verAendern") {
			newDataset = strjoin(Dataset,'\t');
			PartData[PartNr] = exchangePart(PartData[PartNr],newDataset,ATTR_ONLY);
			dlgAccept();
		}
		dlgPushButton("&Alle identischen Bauteile verAendern") {
			newDataset = strjoin(Dataset,'\t');
			changeAllidenticalParts(PartData[PartNr],newDataset, ATTR_ONLY);
			dlgAccept();
		}
		dlgPushButton("-&Cancel") dlgReject();
	};
	
	return strjoin(Dataset,'\t');
}

		
void Vorschlaege(int PartNr, int POnly) {
status("Vorschlaege()");
	int initial_PartNr = PartNr;
	int returnval = 0;
	string Suchbegriff_Package,Suchbegriff_Bezeichnung,Suchbegriff_Hersteller,Orderbase_Nummer; 
	int ist_vorzug = 0;
	int ignore_Case = 1;
	string liste[];
	string PartAttributes[];
	string Bauteil_attribute;
	string temp[],altesBauteil[],neu[],PartDat[];
	int Auswahl,i = 0;
	int PartListAuswahl,altAuswahl,neuAuswahl;
	if(POnly)
		PartNr = str2int(getPartVal(PlaceholderOnly[PartNr],ID)); 
		//am Ende des Datensatzes steht der Index des Bauteils im Kompletten Datensatz

	if(strlen(getPartVal(PartData[PartNr],PACKAGE)) > 0) { //gibt es ein Package für das Device ? (gilt nicht für Versorgungsspannung)
		int n = strsplit(altesBauteil,PartDataRecovery[PartNr],'\t');
		for(i = 0; i < n; i++) {
			PartDat[i] += PartDataValueNames[i] + "\t" + altesBauteil[i] + "\t";
			if(getPartVal(PartData[PartNr],CHANGE_MODE) != int2str(NONE)) {
				PartDat[i] += getPartVal(PartData[PartNr],i);
			}
		}
		if(getPartVal(PartData[PartNr],PREFIX) == "R") {
			Suchbegriff_Package = "RES*";
		} else if(getPartVal(PartData[PartNr],PREFIX) == "C") {
			Suchbegriff_Package = "CAPC*";
		} else {
			Suchbegriff_Package = getPartVal(PartData[PartNr],PACKAGE);
		}
	
		dlgDialog("Bauteil-Suche " + getPartVal(PartData[PartNr],DEVICE_NAME) ) {
			//dlgLabel("Name:" + getPartVal(PartData[PartNr],DEVICE_NAME) + "\nPackage: " + getPartVal(PartData[PartNr],S_S_PACKAGE) + "\nPREFIX:" + getPartVal(PartData[PartNr],PREFIX));
			dlgVBoxLayout{
					dlgHBoxLayout{dlgSpacing(1400);}
				dlgHBoxLayout{
					dlgVBoxLayout{dlgSpacing(300);}
					dlgListView("Attribut\taltes Bauteil\t neues Bauteil",PartDat,PartListAuswahl);
					
					dlgVBoxLayout{
						dlgSpacing(30);
						dlgGridLayout{
							dlgCell(0,0)		dlgLabel("Package");
							dlgCell(0,1)		dlgStringEdit(Suchbegriff_Package);
							dlgCell(1,0)		dlgLabel("Bezeichnung");
							dlgCell(1,1)		dlgStringEdit(Suchbegriff_Bezeichnung);
							dlgCell(2,0)		dlgLabel("Hersteller");
							dlgCell(2,1)		dlgStringEdit(Suchbegriff_Hersteller);
							dlgCell(3,0)		dlgLabel("Orderbase-Nummer");
							dlgCell(3,1)		dlgStringEdit(Orderbase_Nummer);
							dlgCell(4,0)		dlgLabel("Groß-Kleinschreibung\nignorieren");
							dlgCell(4,1)		dlgCheckBox("",ignore_Case);
						}
						dlgSpacing(30);
						dlgPushButton("+&\nsuchen\n")  {
							strsplit(liste,createTable(Suchbegriff_Bezeichnung,Suchbegriff_Package,Suchbegriff_Hersteller,Orderbase_Nummer,ist_vorzug,ignore_Case,PartNr),'\n');
							dlgRedisplay();
						}
						dlgStretch(1);
						if(getPartVal(PartData[PartNr],CHANGE_MODE) != int2str(NONE)) {
						dlgPushButton("Bauteil wiederherstellen"){
							dlgDialog("Frage") {
								dlgLabel("Sollen alle Bauteile dieser\nArt wiederhergestellt werden?");
								dlgPushButton("Ja") {
									changeAllidenticalParts(PartData[PartNr],PartDataRecovery[PartNr],RECOVER);
									dlgAccept();
								}
								dlgPushButton("Nein nur dieses") {
									PartData[PartNr] = PartDataRecovery[PartNr];
									dlgAccept();
								}	
								dlgPushButton("Abbrechen") {
									dlgAccept();
								}		
							};
						}
					}
					}	
					
				}
			
				string Ueberschriften;
				
				for(int i = ORDERBASE_NUMMER;i <= VALUEON_OFF; i++) {
					Ueberschriften += (strlen(Ueberschriften) > 0 ? "\t" : "") + PartDataValueNames[i];
				}
				
				dlgListView(Ueberschriften
										,liste
										,Auswahl) {
					int SUCCESS = dlgDialog(""){
						string PartDat2[];
						for(i = 0; i < n; i++) {
							PartDat2[i] += PartDataValueNames[i] + "\t" + altesBauteil[i] + "\t";
							PartDat2[i] += getPartVal(liste[Auswahl],i);
						}
						dlgLabel("<h1> " + getPartVal(liste[Auswahl],HERSTELLER) + " - " + getPartVal(liste[Auswahl],HERSTELLERNR));
						dlgHBoxLayout{
							dlgListView("Attribut\taltes Bauteil\t neues Bauteil",PartDat2,PartListAuswahl);
							dlgVBoxLayout{
								dlgSpacing(400);
							}
						}
						dlgHBoxLayout{
							dlgStretch(0);
							dlgGridLayout{
								dlgCell(0,0){
									dlgPushButton("Datenblatt aktuelles Bauteil\n") 
									system("cmd /c \""+strrep(altesBauteil[11]+"\"","file:","",START,ONCE));
								}
								dlgCell(0,1){
									dlgPushButton("Datenblatt neues Bauteil\n") 
									system("cmd /c \""+strrep(getPartVal(liste[Auswahl],DATENBLATT)+"\"","file:","",START,ONCE));
								}
								dlgCell(1,0){
									dlgPushButton("&Austauschen\n") {
										if(Check(PartData[PartNr],liste[Auswahl]) == TRUE) {
											PartData[PartNr] = exchangePart(PartData[PartNr],liste[Auswahl],COMPLETE);
											if(POnly) 
												PlaceholderOnly[initial_PartNr] = exchangePart(PlaceholderOnly[initial_PartNr],liste[Auswahl],COMPLETE);
											Bauteil_attribute = PartData[PartNr] ;
											dlgAccept();
										}else{
											dlgReject();
										}
									}
								}
								dlgCell(1,1){
									dlgPushButton("&Alle identischen tauschen\n") {
										if(Check(PartData[PartNr],liste[Auswahl]) == TRUE) {
											changeAllidenticalParts(PartData[PartNr],liste[Auswahl],COMPLETE);
											dlgAccept();
										}else{
											dlgReject();
										}
									}
								}
									
								/* 	dlgPushButton("+&Attribute und Symbol austauschen, Package erhalten") {
										PartData[PartNr] = exchangePart(PartData[PartNr],liste[Auswahl]);
										dlgAccept();
									} */
							/* 		dlgPushButton("+&Footprint austauschen") {
									//Package Befehl -> package C6 
										PartData[PartNr] = exchangePart(PartData[PartNr],liste[Auswahl]);
										dlgAccept();
									} */
								dlgCell(2,0){
									dlgPushButton("&Attribute austauschen\n(Platzhalter erhalten)") {
										if(Check(PartData[PartNr],liste[Auswahl]) == TRUE) {
											PartData[PartNr] = exchangePart(PartData[PartNr],liste[Auswahl],ATTR_ONLY);
											if(POnly) 
												PlaceholderOnly[initial_PartNr] = exchangePart(PlaceholderOnly[initial_PartNr],liste[Auswahl],ATTR_ONLY);
											dlgAccept();	
										}else{
											dlgReject();
										}
									}
								}
								dlgCell(2,1){
									dlgPushButton("Attribute für alle identischen\nBauteile austauschen (Platzhalter erhalten)") {
										if(Check(PartData[PartNr],liste[Auswahl]) == TRUE) {
											changeAllidenticalParts(PartData[PartNr],liste[Auswahl],ATTR_ONLY);
											dlgAccept();
										}else{
											dlgReject();
										}
									}
								}
								dlgCell(3,1) {
									dlgPushButton("-&\nAbbrechen\n") dlgReject();
								}
							}
						}
					};
					if(SUCCESS)	dlgAccept();
				}
			}
			dlgHBoxLayout{
				/*dlgPushButton("eigenen Datensatz anlegen") {
					newDataset(PartNr);
				}*/
				dlgStretch(1);
				dlgPushButton("&OK") {
					dlgAccept();
				}
				dlgPushButton("-&Cancel") {
					dlgReject();
				}
			}
		};		
		
	} else {
		dlgMessageBox("Das Bauteil hat kein Package..");
	}
}
/**
 *  @brief 	Das auszuführende Script mit dem Bauteile ersetzt werden, wird
 *  				mit dieser Funktion erstellt
 *  
 *  @return das Script
 */
string buildScript() {
	string cmd;
	string temp_arr[];
	string lib;
	string currentpage;
	int val;
		
	for(int i = 0; i < Bauteile; i++){
		val = evalChangeMode(getPartVal(PartData[i],CHANGE_MODE));
		int n = strsplit(temp_arr,getPartVal(PartData[i],LIBRARY),'/');
		lib = filesetext(temp_arr[n-1],"");
		string value;
		string mirrored = "";
		string orientation = getPartVal(PartData[i],ORIENTATION);
		if(getPartVal(PartData[i],MIRRORED) == "true") 
			mirrored = "M";
		switch(val){
			case 0: break; //NONE
			case 1: {		//COMPLETE
									//Replace Befehl -> replace C6 'BC817'@'ZE SMD Vorzugsliste'
								cmd += 	"REPLACE " 
												+ getPartVal(PartData[i],PART_NAME) + " '"
												+ getPartVal(PartData[i],DEVICE_NAME) + "@"
												+ lib + "';\n";
								break;
								}
			case 2: break; //ATTR_SYM
			case 3: break; //PACK_ONLY
			case 4: {	//ATTR_ONLY
								if(currentpage != getPartVal(PartData[i],SHEET)) {
									cmd += "EDIT .s"+getPartVal(PartData[i],SHEET)+";\n";
									currentpage = getPartVal(PartData[i],SHEET);
								}
								for(int k = 0; k < 5; k++) {
									if(getPartVal(PartData[i],PartAttribOrder[k]) == "") value = " ";
									else value = getPartVal(PartData[i],PartAttribOrder[k]);
										if(getPartVal(PartDataRecovery[i],PartAttribOrder[k]) != "")
											cmd += 	"ATTRIBUTE "
															+ getPartVal(PartData[i],PART_NAME) + " "
															+ att[k] + " DELETE;\n";
										cmd += 	"ATTRIBUTE " 
														+ getPartVal(PartData[i],PART_NAME) + " "
														+ att[k] + " '"
														+ value + "' "
														+ "R0 (0 0);\n";
									
								}
								
								break;
							}
			default: break;
		
		}
		if(getPartVal(PartData[i],VALU) != "" &&
			val == (COMPLETE ||ATTR_ONLY) &&
			getPartVal(PartData[i],VALUEON_OFF) == "On") {
								if(currentpage != getPartVal(PartData[i],SHEET)) {
									cmd += "EDIT .s"+getPartVal(PartData[i],SHEET)+";\n";
									currentpage = getPartVal(PartData[i],SHEET);
								}
								cmd +=  "VALUE "
											+ getPartVal(PartData[i],PART_NAME) + " '"
											+ getPartVal(PartData[i],VALU) + "';\n";
		}
	}

	return cmd;
}



int MainMenu(int Darstellung) {
status("MainMenu()");
	int Ansicht = (Darstellung & 0x02) ? 1 : 0;
	int MainAuswahl;
	int Platzhalter = (Darstellung & 0x04) ? 1 : 0;
	string Headline;
	if(Darstellung & 0x02) {
		Headline =	strjoin(PartDataValueNames,'\t');
	} else {
		for(int i = 0;i < 7; i++)
			if(Headline == "") {
				Headline += PartDataValueNames[i];
			} else {
				Headline += "\t" +PartDataValueNames[i];
			}
	}
	if(Darstellung & 0x04) {
		dlgDialog("Liste der verwendeten Bauteile") {
			dlgVBoxLayout{
				dlgHBoxLayout{
					dlgVBoxLayout{dlgSpacing(800);}
					dlgVBoxLayout{
						dlgListView(Headline, PlaceholderOnly, MainAuswahl) {
							Vorschlaege(MainAuswahl, 1);
							dlgAccept();
						}
						dlgHBoxLayout{
							dlgCheckBox("&detaillierte Ansich", Ansicht) {
								Darstellung ^= 0x02;
								dlgAccept();
							}
							dlgCheckBox("&nur Platzhalter anzeigen", Platzhalter) {
								Darstellung ^= 0x04;
								dlgAccept();
							}
							if(AenderungenGeschehen) {
								dlgPushButton("&Aenderungen festschreiben") {
									Darstellung = 0;
									dlgAccept();
								}
							}
							dlgPushButton("-&Cancel") {
								Darstellung = 0;
								exit(0);
							}
							dlgPushButton("Hilfe") {
								system("cmd.exe /c \""+ ULP_PATH + "/Platzhalterersetzen_Beschreibung.pdf\"");
							}
						}
					}
				}
			}	
		};
	} else {
		dlgDialog("Liste der verwendeten Bauteile") {
			dlgVBoxLayout{
				dlgHBoxLayout{
					dlgVBoxLayout{dlgSpacing(800);}
					dlgVBoxLayout{
						dlgListView(Headline, PartData, MainAuswahl) {
							Vorschlaege(MainAuswahl, 0);
							dlgAccept();
						}
						dlgHBoxLayout{
							dlgCheckBox("&detaillierte Ansich", Ansicht) {
								Darstellung ^= 0x02;
								dlgAccept();
							}
							dlgCheckBox("&nur Platzhalter anzeigen", Platzhalter) {
								Darstellung ^= 0x04;
								dlgAccept();
							}
							if(AenderungenGeschehen) {
								dlgPushButton("&Aenderungen festschreiben") {
									Darstellung = 0;
									dlgAccept();
								}
							}
							dlgPushButton("-&Cancel") {
								Darstellung = 0;
								exit(0);
							}
							dlgPushButton("Hilfe") {
								system("cmd.exe /c \""+ ULP_PATH + "/Platzhalterersetzen_Beschreibung.pdf\"");
							}
						}
					}
				}
			}	
		};
	}
	return Darstellung;
}

void main() {
	if(schematic) {
		string temp[];
		int returnvalOfMainMenu = 1;
		string cmd;
		fileglob(tempStrArr1,"//win.desy.de/group/sze/public/Eagle_6+/lbr/*.lbr");
		LibList = strjoin(tempStrArr1,'\n');
		fileread(Pac_Sort,"//win.desy.de/group/sze/public/Eagle_6+/ulp/Bauteile_nach_Package_sortiert.csv");
		Bauteile = strsplit(Pac_Sort_Arr, Pac_Sort,'\n');
		fileread(Val_Sort,"//win.desy.de/group/sze/public/Eagle_6+/ulp/Bauteile_nach_Val_sortiert.csv");
		strsplit(Val_Sort_Arr, Val_Sort,'\n');
		getPartData();
		while((returnvalOfMainMenu = MainMenu(returnvalOfMainMenu)));
		cmd = buildScript();
		//debug(cmd);
		if(fileglob(temp,"C:/Users/Scholzj/Desktop/")) 
			output("C:/Users/Scholzj/Desktop/debug.txt", "wt") { 
			printf("%s",cmd); 
		}
		exit(cmd);
	} else {
		exit(0);
	}
}
